package 'CSRM Profile' {
    doc /* Custom stereotypes from the v1 profile, carried over as SysML v2 metadata definitions.
           Tag definitions become attributes; the tool-side behaviour (icons, validation rules,
           derived properties, table customisations) is NOT carried and must be re-created. */
    metadata def Subsystem;
}
